MsgTest DEFINITIONS ::=BEGIN
    Msg ::= SEQUENCE{
	length INTEGER,
        latitude INTEGER,        -- latitude of traffic
        longitude INTEGER,        -- longitude of traffic
	heading INTEGER,
	state INTEGER,
	time INTEGER,
	pading INTEGER
    }
END
